module maplemain {
    yang-version 1;
    namespace "urn:opendaylight:params:xml:ns:yang:maplemain";
    prefix "maplemain";

    revision "2015-01-05" {
        description "Initial revision of maplemain model";
    }
}
